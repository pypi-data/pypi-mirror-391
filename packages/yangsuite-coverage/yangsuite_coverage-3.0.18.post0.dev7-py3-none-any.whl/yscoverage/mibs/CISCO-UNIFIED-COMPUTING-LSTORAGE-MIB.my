-- *********************************************************************
-- CISCO-UNIFIED-COMPUTING-LSTORAGE-MIB.my
-- 
-- MIB representation of the Cisco Unified Computing System
-- LSTORAGE management information model package
-- 
-- Created June 2015 by Charles Bullis
-- 
-- Copyright (c) 2005-2015 Cisco Systems, Inc. All rights reserved.
-- 
-- *********************************************************************

CISCO-UNIFIED-COMPUTING-LSTORAGE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsLsConfigIssues,
    CucsLstorageAdminState,
    CucsLstorageAutoDeploy,
    CucsLstorageAvailability,
    CucsLstorageBootDevice,
    CucsLstorageConfigIssues,
    CucsLstorageConfigState,
    CucsLstorageDasScsiLunStorageClass,
    CucsLstorageLunMapType,
    CucsLstorageVirtualDriveDefAccessPolicy,
    CucsLstorageVirtualDriveDefDriveCache,
    CucsLstorageVirtualDriveDefIoPolicy,
    CucsLstorageVirtualDriveDefReadPolicy,
    CucsLstorageVirtualDriveDefStripSize,
    CucsLstorageVirtualDriveDefWriteCachePolicy,
    CucsPolicyPolicyOwner,
    CucsStorageDiskRole,
    CucsStorageLunType,
    CucsStorageTechnology,
    CucsStorageUnitOperState
        FROM CISCO-UNIFIED-COMPUTING-TC-MIB;

cucsLstorageObjects MODULE-IDENTITY
    LAST-UPDATED    "201506290000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        LSTORAGE management information model package"
    ::= { ciscoUnifiedComputingMIBObjects 79 }

cucsLstorageDasScsiLunTable OBJECT-TYPE
    SYNTAX           SEQUENCE OF CucsLstorageDasScsiLunEntry
    MAX-ACCESS       not-accessible
    STATUS           current
    DESCRIPTION
        "Cisco UCS lstorage:DasScsiLun managed object table"
    ::= { cucsLstorageObjects 14 }

cucsLstorageDasScsiLunEntry OBJECT-TYPE
    SYNTAX           CucsLstorageDasScsiLunEntry
    MAX-ACCESS       not-accessible
    STATUS           current
    DESCRIPTION
        "Entry for the cucsLstorageDasScsiLunTable table."
    INDEX { cucsLstorageDasScsiLunInstanceId }
    ::= { cucsLstorageDasScsiLunTable 1 }

CucsLstorageDasScsiLunEntry ::= SEQUENCE {
    cucsLstorageDasScsiLunInstanceId                                 CucsManagedObjectId,
    cucsLstorageDasScsiLunDn                                         CucsManagedObjectDn,
    cucsLstorageDasScsiLunRn                                         SnmpAdminString,
    cucsLstorageDasScsiLunAdminState                                 CucsLstorageAdminState,
    cucsLstorageDasScsiLunAutoDeploy                                 CucsLstorageAutoDeploy,
    cucsLstorageDasScsiLunBootDev                                    CucsLstorageBootDevice,
    cucsLstorageDasScsiLunConfigQualifier                            CucsLstorageConfigIssues,
    cucsLstorageDasScsiLunConfigState                                CucsLstorageConfigState,
    cucsLstorageDasScsiLunExpandToAvail                              TruthValue,
    cucsLstorageDasScsiLunLocalDiskPolicyName                        SnmpAdminString,
    cucsLstorageDasScsiLunLunDn                                      SnmpAdminString,
    cucsLstorageDasScsiLunLunMapType                                 CucsLstorageLunMapType,
    cucsLstorageDasScsiLunName                                       SnmpAdminString,
    cucsLstorageDasScsiLunOperLocalDiskPolicyName                    SnmpAdminString,
    cucsLstorageDasScsiLunOperState                                  CucsStorageOperState,
    cucsLstorageDasScsiLunOrder                                      Gauge32,
    cucsLstorageDasScsiLunSize                                       Unsigned64,
    cucsLstorageDasScsiLunStorageClass                               CucsLstorageDasScsiLunStorageClass,
    cucsLstorageDasScsiLunDeferredNaming                             TruthValue
}

cucsLstorageDasScsiLunInstanceId OBJECT-TYPE
    SYNTAX       CucsManagedObjectId
    MAX-ACCESS   not-accessible
    STATUS       current
    DESCRIPTION
        "Instance identifier of the managed object."
    ::= { cucsLstorageDasScsiLunEntry 1 }

cucsLstorageDasScsiLunDn OBJECT-TYPE
    SYNTAX       CucsManagedObjectDn
    MAX-ACCESS   read-only
    STATUS       current
    DESCRIPTION
        "Cisco UCS lstorage:DasScsiLun:dn managed object property"
    ::= { cucsLstorageDasScsiLunEntry 2 }

cucsLstorageDasScsiLunRn OBJECT-TYPE
    SYNTAX       SnmpAdminString
    MAX-ACCESS   read-only
    STATUS       current
    DESCRIPTION
        "Cisco UCS lstorage:DasScsiLun:rn managed object property"
    ::= { cucsLstorageDasScsiLunEntry 3 }

cucsLstorageDasScsiLunAdminState OBJECT-TYPE
    SYNTAX       CucsLstorageAdminState
    MAX-ACCESS   read-only
    STATUS       current
    DESCRIPTION
        "Cisco UCS lstorage:DasScsiLun:adminState managed object property"
    ::= { cucsLstorageDasScsiLunEntry 4 }

cucsLstorageDasScsiLunAutoDeploy OBJECT-TYPE
    SYNTAX       CucsLstorageAutoDeploy
    MAX-ACCESS   read-only
    STATUS       current
    DESCRIPTION
        "Cisco UCS lstorage:DasScsiLun:autoDeploy managed object property"
    ::= { cucsLstorageDasScsiLunEntry 5 }

cucsLstorageDasScsiLunBootDev OBJECT-TYPE
    SYNTAX       CucsLstorageBootDevice
    MAX-ACCESS   read-only
    STATUS       current
    DESCRIPTION
        "Cisco UCS lstorage:DasScsiLun:bootDev managed object property"
    ::= { cucsLstorageDasScsiLunEntry 6 }

cucsLstorageDasScsiLunConfigQualifier OBJECT-TYPE
    SYNTAX       CucsLstorageConfigIssues
    MAX-ACCESS   read-only
    STATUS       current
    DESCRIPTION
        "Cisco UCS lstorage:DasScsiLun:configQualifier
        managed object property"
    ::= { cucsLstorageDasScsiLunEntry 7 }

cucsLstorageDasScsiLunConfigState OBJECT-TYPE
    SYNTAX       CucsLstorageConfigState
    MAX-ACCESS   read-only
    STATUS       current
    DESCRIPTION
        "Cisco UCS lstorage:DasScsiLun:configState managed
        object property"
    ::= { cucsLstorageDasScsiLunEntry 8 }

cucsLstorageDasScsiLunExpandToAvail OBJECT-TYPE
    SYNTAX       TruthValue
    MAX-ACCESS   read-only
    STATUS       current
    DESCRIPTION
        "Cisco UCS lstorage:DasScsiLun:expandToAvail managed
        object property"
    ::= { cucsLstorageDasScsiLunEntry 9 }

cucsLstorageDasScsiLunLocalDiskPolicyName OBJECT-TYPE
    SYNTAX       SnmpAdminString
    MAX-ACCESS   read-only
    STATUS       current
    DESCRIPTION
        "Cisco UCS lstorage:DasScsiLun:localDiskPolicyName
        managed object property"
    ::= { cucsLstorageDasScsiLunEntry 10 }

cucsLstorageDasScsiLunLunDn OBJECT-TYPE
    SYNTAX       SnmpAdminString
    MAX-ACCESS   read-only
    STATUS       current
    DESCRIPTION
        "Cisco UCS lstorage:DasScsiLun:lunDn managed object property"
    ::= { cucsLstorageDasScsiLunEntry 11 }

cucsLstorageDasScsiLunLunMapType OBJECT-TYPE
    SYNTAX       CucsLstorageLunMapType
    MAX-ACCESS   read-only
    STATUS       current
    DESCRIPTION
        "Cisco UCS lstorage:DasScsiLun:lunMapType managed object property"
    ::= { cucsLstorageDasScsiLunEntry 12 }

cucsLstorageDasScsiLunName OBJECT-TYPE
    SYNTAX       SnmpAdminString
    MAX-ACCESS   read-only
    STATUS       current
    DESCRIPTION
        "Cisco UCS lstorage:DasScsiLun:name managed object property"
    ::= { cucsLstorageDasScsiLunEntry 13 }

cucsLstorageDasScsiLunOperLocalDiskPolicyName OBJECT-TYPE
    SYNTAX       SnmpAdminString
    MAX-ACCESS   read-only
    STATUS       current
    DESCRIPTION
        "Cisco UCS lstorage:DasScsiLun:operLocalDiskPolicyName
        managed object property"
    ::= { cucsLstorageDasScsiLunEntry 14 }

cucsLstorageDasScsiLunOperState OBJECT-TYPE
    SYNTAX       CucsStorageOperState
    MAX-ACCESS   read-only
    STATUS       current
    DESCRIPTION
        "Cisco UCS lstorage:DasScsiLun:operState managed object property"
    ::= { cucsLstorageDasScsiLunEntry 15 }

cucsLstorageDasScsiLunOrder OBJECT-TYPE
    SYNTAX       Gauge32
    MAX-ACCESS   read-only
    STATUS       current
    DESCRIPTION
        "Cisco UCS lstorage:DasScsiLun:order managed object property"
    ::= { cucsLstorageDasScsiLunEntry 16 }

cucsLstorageDasScsiLunSize OBJECT-TYPE
    SYNTAX       Unsigned64
    MAX-ACCESS   read-only
    STATUS       current
    DESCRIPTION
        "Cisco UCS lstorage:DasScsiLun:size managed object property"
    ::= { cucsLstorageDasScsiLunEntry 17 }

cucsLstorageDasScsiLunStorageClass OBJECT-TYPE
    SYNTAX       CucsLstorageDasScsiLunStorageClass
    MAX-ACCESS   read-only
    STATUS       current
    DESCRIPTION
        "Cisco UCS lstorage:DasScsiLun:storageClass managed
        object property"
    ::= { cucsLstorageDasScsiLunEntry 18 }

cucsLstorageDasScsiLunDeferredNaming OBJECT-TYPE
    SYNTAX       TruthValue
    MAX-ACCESS   read-only
    STATUS       current
    DESCRIPTION
        "Cisco UCS lstorage:DasScsiLun:deferredNaming managed
        object property"
    ::= { cucsLstorageDasScsiLunEntry 19 }

cucsLstorageDiskGroupConfigDefTable OBJECT-TYPE
    SYNTAX           SEQUENCE OF CucsLstorageDiskGroupConfigDefEntry
    MAX-ACCESS       not-accessible
    STATUS           current
    DESCRIPTION
        "Cisco UCS lstorage:DiskGroupConfigDef managed object table"
    ::= { cucsLstorageObjects 15 }

cucsLstorageDiskGroupConfigDefEntry OBJECT-TYPE
    SYNTAX           CucsLstorageDiskGroupConfigDefEntry
    MAX-ACCESS       not-accessible
    STATUS           current
    DESCRIPTION
        "Entry for the cucsLstorageDiskGroupConfigDefTable table."
    INDEX { cucsLstorageDiskGroupConfigDefInstanceId }
    ::= { cucsLstorageDiskGroupConfigDefTable 1 }

CucsLstorageDiskGroupConfigDefEntry ::= SEQUENCE {
    cucsLstorageDiskGroupConfigDefInstanceId                         CucsManagedObjectId,
    cucsLstorageDiskGroupConfigDefDn                                 CucsManagedObjectDn,
    cucsLstorageDiskGroupConfigDefRn                                 SnmpAdminString,
    cucsLstorageDiskGroupConfigDefDescr                              SnmpAdminString,
    cucsLstorageDiskGroupConfigDefIntId                              SnmpAdminString,
    cucsLstorageDiskGroupConfigDefName                               SnmpAdminString,
    cucsLstorageDiskGroupConfigDefPolicyLevel                        Gauge32,
    cucsLstorageDiskGroupConfigDefPolicyOwner                        CucsPolicyPolicyOwner,
    cucsLstorageDiskGroupConfigDefRaidLevel                          CucsStorageLunType,
    cucsLstorageDiskGroupConfigDefDeployOnUpdate                     TruthValue
}

cucsLstorageDiskGroupConfigDefInstanceId OBJECT-TYPE
    SYNTAX       CucsManagedObjectId
    MAX-ACCESS   not-accessible
    STATUS       current
    DESCRIPTION
        "Instance identifier of the managed object."
    ::= { cucsLstorageDiskGroupConfigDefEntry 1 }

cucsLstorageDiskGroupConfigDefDn OBJECT-TYPE
    SYNTAX       CucsManagedObjectDn
    MAX-ACCESS   read-only
    STATUS       current
    DESCRIPTION
        "Cisco UCS lstorage:DiskGroupConfigDef:dn managed object property"
    ::= { cucsLstorageDiskGroupConfigDefEntry 2 }

cucsLstorageDiskGroupConfigDefRn OBJECT-TYPE
    SYNTAX       SnmpAdminString
    MAX-ACCESS   read-only
    STATUS       current
    DESCRIPTION
        "Cisco UCS lstorage:DiskGroupConfigDef:rn managed object property"
    ::= { cucsLstorageDiskGroupConfigDefEntry 3 }

cucsLstorageDiskGroupConfigDefDescr OBJECT-TYPE
    SYNTAX       SnmpAdminString
    MAX-ACCESS   read-only
    STATUS       current
    DESCRIPTION
        "Cisco UCS lstorage:DiskGroupConfigDef:descr managed
        object property"
    ::= { cucsLstorageDiskGroupConfigDefEntry 4 }

cucsLstorageDiskGroupConfigDefIntId OBJECT-TYPE
    SYNTAX       SnmpAdminString
    MAX-ACCESS   read-only
    STATUS       current
    DESCRIPTION
        "Cisco UCS lstorage:DiskGroupConfigDef:intId managed
        object property"
    ::= { cucsLstorageDiskGroupConfigDefEntry 5 }

cucsLstorageDiskGroupConfigDefName OBJECT-TYPE
    SYNTAX       SnmpAdminString
    MAX-ACCESS   read-only
    STATUS       current
    DESCRIPTION
        "Cisco UCS lstorage:DiskGroupConfigDef:name managed
        object property"
    ::= { cucsLstorageDiskGroupConfigDefEntry 6 }

cucsLstorageDiskGroupConfigDefPolicyLevel OBJECT-TYPE
    SYNTAX       Gauge32
    MAX-ACCESS   read-only
    STATUS       current
    DESCRIPTION
        "Cisco UCS lstorage:DiskGroupConfigDef:policyLevel
        managed object property"
    ::= { cucsLstorageDiskGroupConfigDefEntry 7 }

cucsLstorageDiskGroupConfigDefPolicyOwner OBJECT-TYPE
    SYNTAX       CucsPolicyPolicyOwner
    MAX-ACCESS   read-only
    STATUS       current
    DESCRIPTION
        "Cisco UCS lstorage:DiskGroupConfigDef:policyOwner
        managed object property"
    ::= { cucsLstorageDiskGroupConfigDefEntry 8 }

cucsLstorageDiskGroupConfigDefRaidLevel OBJECT-TYPE
    SYNTAX       CucsStorageLunType
    MAX-ACCESS   read-only
    STATUS       current
    DESCRIPTION
        "Cisco UCS lstorage:DiskGroupConfigDef:raidLevel
        managed object property"
    ::= { cucsLstorageDiskGroupConfigDefEntry 9 }

cucsLstorageDiskGroupConfigDefDeployOnUpdate OBJECT-TYPE
    SYNTAX       TruthValue
    MAX-ACCESS   read-only
    STATUS       current
    DESCRIPTION
        "Cisco UCS lstorage:DiskGroupConfigDef:deployOnUpdate
        managed object property"
    ::= { cucsLstorageDiskGroupConfigDefEntry 10 }

cucsLstorageDiskGroupConfigPolicyTable OBJECT-TYPE
    SYNTAX           SEQUENCE OF CucsLstorageDiskGroupConfigPolicyEntry
    MAX-ACCESS       not-accessible
    STATUS           current
    DESCRIPTION
        "Cisco UCS lstorage:DiskGroupConfigPolicy managed object table"
    ::= { cucsLstorageObjects 16 }

cucsLstorageDiskGroupConfigPolicyEntry OBJECT-TYPE
    SYNTAX           CucsLstorageDiskGroupConfigPolicyEntry
    MAX-ACCESS       not-accessible
    STATUS           current
    DESCRIPTION
        "Entry for the cucsLstorageDiskGroupConfigPolicyTable table."
    INDEX { cucsLstorageDiskGroupConfigPolicyInstanceId }
    ::= { cucsLstorageDiskGroupConfigPolicyTable 1 }

CucsLstorageDiskGroupConfigPolicyEntry ::= SEQUENCE {
    cucsLstorageDiskGroupConfigPolicyInstanceId                      CucsManagedObjectId,
    cucsLstorageDiskGroupConfigPolicyDn                              CucsManagedObjectDn,
    cucsLstorageDiskGroupConfigPolicyRn                              SnmpAdminString,
    cucsLstorageDiskGroupConfigPolicyDescr                           SnmpAdminString,
    cucsLstorageDiskGroupConfigPolicyIntId                           SnmpAdminString,
    cucsLstorageDiskGroupConfigPolicyName                            SnmpAdminString,
    cucsLstorageDiskGroupConfigPolicyPolicyLevel                     Gauge32,
    cucsLstorageDiskGroupConfigPolicyPolicyOwner                     CucsPolicyPolicyOwner,
    cucsLstorageDiskGroupConfigPolicyRaidLevel                       CucsStorageLunType,
    cucsLstorageDiskGroupConfigPolicyDeployOnUpdate                  TruthValue
}

cucsLstorageDiskGroupConfigPolicyInstanceId OBJECT-TYPE
    SYNTAX       CucsManagedObjectId
    MAX-ACCESS   not-accessible
    STATUS       current
    DESCRIPTION
        "Instance identifier of the managed object."
    ::= { cucsLstorageDiskGroupConfigPolicyEntry 1 }

cucsLstorageDiskGroupConfigPolicyDn OBJECT-TYPE
    SYNTAX       CucsManagedObjectDn
    MAX-ACCESS   read-only
    STATUS       current
    DESCRIPTION
        "Cisco UCS lstorage:DiskGroupConfigPolicy:dn managed
        object property"
    ::= { cucsLstorageDiskGroupConfigPolicyEntry 2 }

cucsLstorageDiskGroupConfigPolicyRn OBJECT-TYPE
    SYNTAX       SnmpAdminString
    MAX-ACCESS   read-only
    STATUS       current
    DESCRIPTION
        "Cisco UCS lstorage:DiskGroupConfigPolicy:rn managed
        object property"
    ::= { cucsLstorageDiskGroupConfigPolicyEntry 3 }

cucsLstorageDiskGroupConfigPolicyDescr OBJECT-TYPE
    SYNTAX       SnmpAdminString
    MAX-ACCESS   read-only
    STATUS       current
    DESCRIPTION
        "Cisco UCS lstorage:DiskGroupConfigPolicy:descr
        managed object property"
    ::= { cucsLstorageDiskGroupConfigPolicyEntry 4 }

cucsLstorageDiskGroupConfigPolicyIntId OBJECT-TYPE
    SYNTAX       SnmpAdminString
    MAX-ACCESS   read-only
    STATUS       current
    DESCRIPTION
        "Cisco UCS lstorage:DiskGroupConfigPolicy:intId
        managed object property"
    ::= { cucsLstorageDiskGroupConfigPolicyEntry 5 }

cucsLstorageDiskGroupConfigPolicyName OBJECT-TYPE
    SYNTAX       SnmpAdminString
    MAX-ACCESS   read-only
    STATUS       current
    DESCRIPTION
        "Cisco UCS lstorage:DiskGroupConfigPolicy:name
        managed object property"
    ::= { cucsLstorageDiskGroupConfigPolicyEntry 6 }

cucsLstorageDiskGroupConfigPolicyPolicyLevel OBJECT-TYPE
    SYNTAX       Gauge32
    MAX-ACCESS   read-only
    STATUS       current
    DESCRIPTION
        "Cisco UCS lstorage:DiskGroupConfigPolicy:policyLevel
        managed object property"
    ::= { cucsLstorageDiskGroupConfigPolicyEntry 7 }

cucsLstorageDiskGroupConfigPolicyPolicyOwner OBJECT-TYPE
    SYNTAX       CucsPolicyPolicyOwner
    MAX-ACCESS   read-only
    STATUS       current
    DESCRIPTION
        "Cisco UCS lstorage:DiskGroupConfigPolicy:policyOwner
        managed object property"
    ::= { cucsLstorageDiskGroupConfigPolicyEntry 8 }

cucsLstorageDiskGroupConfigPolicyRaidLevel OBJECT-TYPE
    SYNTAX       CucsStorageLunType
    MAX-ACCESS   read-only
    STATUS       current
    DESCRIPTION
        "Cisco UCS lstorage:DiskGroupConfigPolicy:raidLevel
        managed object property"
    ::= { cucsLstorageDiskGroupConfigPolicyEntry 9 }

cucsLstorageDiskGroupConfigPolicyDeployOnUpdate OBJECT-TYPE
    SYNTAX       TruthValue
    MAX-ACCESS   read-only
    STATUS       current
    DESCRIPTION
        "Cisco UCS lstorage:DiskGroupConfigPolicy:deployOnUpdate
        managed object property"
    ::= { cucsLstorageDiskGroupConfigPolicyEntry 10 }

cucsLstorageDiskGroupQualifierTable OBJECT-TYPE
    SYNTAX           SEQUENCE OF CucsLstorageDiskGroupQualifierEntry
    MAX-ACCESS       not-accessible
    STATUS           current
    DESCRIPTION
        "Cisco UCS lstorage:DiskGroupQualifier managed object table"
    ::= { cucsLstorageObjects 17 }

cucsLstorageDiskGroupQualifierEntry OBJECT-TYPE
    SYNTAX           CucsLstorageDiskGroupQualifierEntry
    MAX-ACCESS       not-accessible
    STATUS           current
    DESCRIPTION
        "Entry for the cucsLstorageDiskGroupQualifierTable table."
    INDEX { cucsLstorageDiskGroupQualifierInstanceId }
    ::= { cucsLstorageDiskGroupQualifierTable 1 }

CucsLstorageDiskGroupQualifierEntry ::= SEQUENCE {
    cucsLstorageDiskGroupQualifierInstanceId                         CucsManagedObjectId,
    cucsLstorageDiskGroupQualifierDn                                 CucsManagedObjectDn,
    cucsLstorageDiskGroupQualifierRn                                 SnmpAdminString,
    cucsLstorageDiskGroupQualifierDriveType                          CucsStorageTechnology,
    cucsLstorageDiskGroupQualifierMinDriveSize                       Unsigned64,
    cucsLstorageDiskGroupQualifierNumDedHotSpares                    Gauge32,
    cucsLstorageDiskGroupQualifierNumDrives                          Gauge32,
    cucsLstorageDiskGroupQualifierNumGlobHotSpares                   Gauge32,
    cucsLstorageDiskGroupQualifierUseRemainingDisks                  TruthValue
}

cucsLstorageDiskGroupQualifierInstanceId OBJECT-TYPE
    SYNTAX       CucsManagedObjectId
    MAX-ACCESS   not-accessible
    STATUS       current
    DESCRIPTION
        "Instance identifier of the managed object."
    ::= { cucsLstorageDiskGroupQualifierEntry 1 }

cucsLstorageDiskGroupQualifierDn OBJECT-TYPE
    SYNTAX       CucsManagedObjectDn
    MAX-ACCESS   read-only
    STATUS       current
    DESCRIPTION
        "Cisco UCS lstorage:DiskGroupQualifier:dn managed object property"
    ::= { cucsLstorageDiskGroupQualifierEntry 2 }

cucsLstorageDiskGroupQualifierRn OBJECT-TYPE
    SYNTAX       SnmpAdminString
    MAX-ACCESS   read-only
    STATUS       current
    DESCRIPTION
        "Cisco UCS lstorage:DiskGroupQualifier:rn managed object property"
    ::= { cucsLstorageDiskGroupQualifierEntry 3 }

cucsLstorageDiskGroupQualifierDriveType OBJECT-TYPE
    SYNTAX       CucsStorageTechnology
    MAX-ACCESS   read-only
    STATUS       current
    DESCRIPTION
        "Cisco UCS lstorage:DiskGroupQualifier:driveType
        managed object property"
    ::= { cucsLstorageDiskGroupQualifierEntry 4 }

cucsLstorageDiskGroupQualifierMinDriveSize OBJECT-TYPE
    SYNTAX       Unsigned64
    MAX-ACCESS   read-only
    STATUS       current
    DESCRIPTION
        "Cisco UCS lstorage:DiskGroupQualifier:minDriveSize
        managed object property"
    ::= { cucsLstorageDiskGroupQualifierEntry 5 }

cucsLstorageDiskGroupQualifierNumDedHotSpares OBJECT-TYPE
    SYNTAX       Gauge32
    MAX-ACCESS   read-only
    STATUS       current
    DESCRIPTION
        "Cisco UCS lstorage:DiskGroupQualifier:numDedHotSpares
        managed object property"
    ::= { cucsLstorageDiskGroupQualifierEntry 6 }

cucsLstorageDiskGroupQualifierNumDrives OBJECT-TYPE
    SYNTAX       Gauge32
    MAX-ACCESS   read-only
    STATUS       current
    DESCRIPTION
        "Cisco UCS lstorage:DiskGroupQualifier:numDrives
        managed object property"
    ::= { cucsLstorageDiskGroupQualifierEntry 7 }

cucsLstorageDiskGroupQualifierNumGlobHotSpares OBJECT-TYPE
    SYNTAX       Gauge32
    MAX-ACCESS   read-only
    STATUS       current
    DESCRIPTION
        "Cisco UCS lstorage:DiskGroupQualifier:numGlobHotSpares
        managed object property"
    ::= { cucsLstorageDiskGroupQualifierEntry 8 }

cucsLstorageDiskGroupQualifierUseRemainingDisks OBJECT-TYPE
    SYNTAX       TruthValue
    MAX-ACCESS   read-only
    STATUS       current
    DESCRIPTION
        "Cisco UCS lstorage:DiskGroupQualifier:useRemainingDisks
        managed object property"
    ::= { cucsLstorageDiskGroupQualifierEntry 9 }

cucsLstorageLocalDiskConfigRefTable OBJECT-TYPE
    SYNTAX           SEQUENCE OF CucsLstorageLocalDiskConfigRefEntry
    MAX-ACCESS       not-accessible
    STATUS           current
    DESCRIPTION
        "Cisco UCS lstorage:LocalDiskConfigRef managed object table"
    ::= { cucsLstorageObjects 21 }

cucsLstorageLocalDiskConfigRefEntry OBJECT-TYPE
    SYNTAX           CucsLstorageLocalDiskConfigRefEntry
    MAX-ACCESS       not-accessible
    STATUS           current
    DESCRIPTION
        "Entry for the cucsLstorageLocalDiskConfigRefTable table."
    INDEX { cucsLstorageLocalDiskConfigRefInstanceId }
    ::= { cucsLstorageLocalDiskConfigRefTable 1 }

CucsLstorageLocalDiskConfigRefEntry ::= SEQUENCE {
    cucsLstorageLocalDiskConfigRefInstanceId                         CucsManagedObjectId,
    cucsLstorageLocalDiskConfigRefDn                                 CucsManagedObjectDn,
    cucsLstorageLocalDiskConfigRefRn                                 SnmpAdminString,
    cucsLstorageLocalDiskConfigRefRole                               CucsStorageDiskRole,
    cucsLstorageLocalDiskConfigRefSlotNum                            Gauge32,
    cucsLstorageLocalDiskConfigRefSpanId                             Gauge32
}

cucsLstorageLocalDiskConfigRefInstanceId OBJECT-TYPE
    SYNTAX       CucsManagedObjectId
    MAX-ACCESS   not-accessible
    STATUS       current
    DESCRIPTION
        "Instance identifier of the managed object."
    ::= { cucsLstorageLocalDiskConfigRefEntry 1 }

cucsLstorageLocalDiskConfigRefDn OBJECT-TYPE
    SYNTAX       CucsManagedObjectDn
    MAX-ACCESS   read-only
    STATUS       current
    DESCRIPTION
        "Cisco UCS lstorage:LocalDiskConfigRef:dn managed object property"
    ::= { cucsLstorageLocalDiskConfigRefEntry 2 }

cucsLstorageLocalDiskConfigRefRn OBJECT-TYPE
    SYNTAX       SnmpAdminString
    MAX-ACCESS   read-only
    STATUS       current
    DESCRIPTION
        "Cisco UCS lstorage:LocalDiskConfigRef:rn managed object property"
    ::= { cucsLstorageLocalDiskConfigRefEntry 3 }

cucsLstorageLocalDiskConfigRefRole OBJECT-TYPE
    SYNTAX       CucsStorageDiskRole
    MAX-ACCESS   read-only
    STATUS       current
    DESCRIPTION
        "Cisco UCS lstorage:LocalDiskConfigRef:role managed
        object property"
    ::= { cucsLstorageLocalDiskConfigRefEntry 4 }

cucsLstorageLocalDiskConfigRefSlotNum OBJECT-TYPE
    SYNTAX       Gauge32
    MAX-ACCESS   read-only
    STATUS       current
    DESCRIPTION
        "Cisco UCS lstorage:LocalDiskConfigRef:slotNum
        managed object property"
    ::= { cucsLstorageLocalDiskConfigRefEntry 5 }

cucsLstorageLocalDiskConfigRefSpanId OBJECT-TYPE
    SYNTAX       Gauge32
    MAX-ACCESS   read-only
    STATUS       current
    DESCRIPTION
        "Cisco UCS lstorage:LocalDiskConfigRef:spanId managed
        object property"
    ::= { cucsLstorageLocalDiskConfigRefEntry 6 }

cucsLstorageLocalDiskRefTable OBJECT-TYPE
    SYNTAX           SEQUENCE OF CucsLstorageLocalDiskRefEntry
    MAX-ACCESS       not-accessible
    STATUS           current
    DESCRIPTION
        "Cisco UCS lstorage:LocalDiskRef managed object table"
    ::= { cucsLstorageObjects 22 }

cucsLstorageLocalDiskRefEntry OBJECT-TYPE
    SYNTAX           CucsLstorageLocalDiskRefEntry
    MAX-ACCESS       not-accessible
    STATUS           current
    DESCRIPTION
        "Entry for the cucsLstorageLocalDiskRefTable table."
    INDEX { cucsLstorageLocalDiskRefInstanceId }
    ::= { cucsLstorageLocalDiskRefTable 1 }

CucsLstorageLocalDiskRefEntry ::= SEQUENCE {
    cucsLstorageLocalDiskRefInstanceId                               CucsManagedObjectId,
    cucsLstorageLocalDiskRefDn                                       CucsManagedObjectDn,
    cucsLstorageLocalDiskRefRn                                       SnmpAdminString,
    cucsLstorageLocalDiskRefEnclosureId                              Gauge32,
    cucsLstorageLocalDiskRefSlotId                                   Gauge32
}

cucsLstorageLocalDiskRefInstanceId OBJECT-TYPE
    SYNTAX       CucsManagedObjectId
    MAX-ACCESS   not-accessible
    STATUS       current
    DESCRIPTION
        "Instance identifier of the managed object."
    ::= { cucsLstorageLocalDiskRefEntry 1 }

cucsLstorageLocalDiskRefDn OBJECT-TYPE
    SYNTAX       CucsManagedObjectDn
    MAX-ACCESS   read-only
    STATUS       current
    DESCRIPTION
        "Cisco UCS lstorage:LocalDiskRef:dn managed object property"
    ::= { cucsLstorageLocalDiskRefEntry 2 }

cucsLstorageLocalDiskRefRn OBJECT-TYPE
    SYNTAX       SnmpAdminString
    MAX-ACCESS   read-only
    STATUS       current
    DESCRIPTION
        "Cisco UCS lstorage:LocalDiskRef:rn managed object property"
    ::= { cucsLstorageLocalDiskRefEntry 3 }

cucsLstorageLocalDiskRefEnclosureId OBJECT-TYPE
    SYNTAX       Gauge32
    MAX-ACCESS   read-only
    STATUS       current
    DESCRIPTION
        "Cisco UCS lstorage:LocalDiskRef:enclosureId managed
        object property"
    ::= { cucsLstorageLocalDiskRefEntry 4 }

cucsLstorageLocalDiskRefSlotId OBJECT-TYPE
    SYNTAX       Gauge32
    MAX-ACCESS   read-only
    STATUS       current
    DESCRIPTION
        "Cisco UCS lstorage:LocalDiskRef:slotId managed object property"
    ::= { cucsLstorageLocalDiskRefEntry 5 }

cucsLstorageProfileTable OBJECT-TYPE
    SYNTAX           SEQUENCE OF CucsLstorageProfileEntry
    MAX-ACCESS       not-accessible
    STATUS           current
    DESCRIPTION
        "Cisco UCS lstorage:Profile managed object table"
    ::= { cucsLstorageObjects 37 }

cucsLstorageProfileEntry OBJECT-TYPE
    SYNTAX           CucsLstorageProfileEntry
    MAX-ACCESS       not-accessible
    STATUS           current
    DESCRIPTION
        "Entry for the cucsLstorageProfileTable table."
    INDEX { cucsLstorageProfileInstanceId }
    ::= { cucsLstorageProfileTable 1 }

CucsLstorageProfileEntry ::= SEQUENCE {
    cucsLstorageProfileInstanceId                                    CucsManagedObjectId,
    cucsLstorageProfileDn                                            CucsManagedObjectDn,
    cucsLstorageProfileRn                                            SnmpAdminString,
    cucsLstorageProfileAssignedToDn                                  SnmpAdminString,
    cucsLstorageProfileAvailability                                  CucsLstorageAvailability,
    cucsLstorageProfileDescr                                         SnmpAdminString,
    cucsLstorageProfileIntId                                         SnmpAdminString,
    cucsLstorageProfileName                                          SnmpAdminString,
    cucsLstorageProfilePolicyLevel                                   Gauge32,
    cucsLstorageProfilePolicyOwner                                   CucsPolicyPolicyOwner
}

cucsLstorageProfileInstanceId OBJECT-TYPE
    SYNTAX       CucsManagedObjectId
    MAX-ACCESS   not-accessible
    STATUS       current
    DESCRIPTION
        "Instance identifier of the managed object."
    ::= { cucsLstorageProfileEntry 1 }

cucsLstorageProfileDn OBJECT-TYPE
    SYNTAX       CucsManagedObjectDn
    MAX-ACCESS   read-only
    STATUS       current
    DESCRIPTION
        "Cisco UCS lstorage:Profile:dn managed object property"
    ::= { cucsLstorageProfileEntry 2 }

cucsLstorageProfileRn OBJECT-TYPE
    SYNTAX       SnmpAdminString
    MAX-ACCESS   read-only
    STATUS       current
    DESCRIPTION
        "Cisco UCS lstorage:Profile:rn managed object property"
    ::= { cucsLstorageProfileEntry 3 }

cucsLstorageProfileAssignedToDn OBJECT-TYPE
    SYNTAX       SnmpAdminString
    MAX-ACCESS   read-only
    STATUS       current
    DESCRIPTION
        "Cisco UCS lstorage:Profile:assignedToDn managed object property"
    ::= { cucsLstorageProfileEntry 4 }

cucsLstorageProfileAvailability OBJECT-TYPE
    SYNTAX       CucsLstorageAvailability
    MAX-ACCESS   read-only
    STATUS       current
    DESCRIPTION
        "Cisco UCS lstorage:Profile:availability managed object property"
    ::= { cucsLstorageProfileEntry 5 }

cucsLstorageProfileDescr OBJECT-TYPE
    SYNTAX       SnmpAdminString
    MAX-ACCESS   read-only
    STATUS       current
    DESCRIPTION
        "Cisco UCS lstorage:Profile:descr managed object property"
    ::= { cucsLstorageProfileEntry 6 }

cucsLstorageProfileIntId OBJECT-TYPE
    SYNTAX       SnmpAdminString
    MAX-ACCESS   read-only
    STATUS       current
    DESCRIPTION
        "Cisco UCS lstorage:Profile:intId managed object property"
    ::= { cucsLstorageProfileEntry 7 }

cucsLstorageProfileName OBJECT-TYPE
    SYNTAX       SnmpAdminString
    MAX-ACCESS   read-only
    STATUS       current
    DESCRIPTION
        "Cisco UCS lstorage:Profile:name managed object property"
    ::= { cucsLstorageProfileEntry 8 }

cucsLstorageProfilePolicyLevel OBJECT-TYPE
    SYNTAX       Gauge32
    MAX-ACCESS   read-only
    STATUS       current
    DESCRIPTION
        "Cisco UCS lstorage:Profile:policyLevel managed object property"
    ::= { cucsLstorageProfileEntry 9 }

cucsLstorageProfilePolicyOwner OBJECT-TYPE
    SYNTAX       CucsPolicyPolicyOwner
    MAX-ACCESS   read-only
    STATUS       current
    DESCRIPTION
        "Cisco UCS lstorage:Profile:policyOwner managed object property"
    ::= { cucsLstorageProfileEntry 10 }

cucsLstorageProfileBindingTable OBJECT-TYPE
    SYNTAX           SEQUENCE OF CucsLstorageProfileBindingEntry
    MAX-ACCESS       not-accessible
    STATUS           current
    DESCRIPTION
        "Cisco UCS lstorage:ProfileBinding managed object table"
    ::= { cucsLstorageObjects 38 }

cucsLstorageProfileBindingEntry OBJECT-TYPE
    SYNTAX           CucsLstorageProfileBindingEntry
    MAX-ACCESS       not-accessible
    STATUS           current
    DESCRIPTION
        "Entry for the cucsLstorageProfileBindingTable table."
    INDEX { cucsLstorageProfileBindingInstanceId }
    ::= { cucsLstorageProfileBindingTable 1 }

CucsLstorageProfileBindingEntry ::= SEQUENCE {
    cucsLstorageProfileBindingInstanceId                             CucsManagedObjectId,
    cucsLstorageProfileBindingDn                                     CucsManagedObjectDn,
    cucsLstorageProfileBindingRn                                     SnmpAdminString,
    cucsLstorageProfileBindingIssues                                 CucsLsConfigIssues,
    cucsLstorageProfileBindingName                                   SnmpAdminString,
    cucsLstorageProfileBindingOperStorageProfileName                 SnmpAdminString,
    cucsLstorageProfileBindingStorageProfileName                     SnmpAdminString
}

cucsLstorageProfileBindingInstanceId OBJECT-TYPE
    SYNTAX       CucsManagedObjectId
    MAX-ACCESS   not-accessible
    STATUS       current
    DESCRIPTION
        "Instance identifier of the managed object."
    ::= { cucsLstorageProfileBindingEntry 1 }

cucsLstorageProfileBindingDn OBJECT-TYPE
    SYNTAX       CucsManagedObjectDn
    MAX-ACCESS   read-only
    STATUS       current
    DESCRIPTION
        "Cisco UCS lstorage:ProfileBinding:dn managed object property"
    ::= { cucsLstorageProfileBindingEntry 2 }

cucsLstorageProfileBindingRn OBJECT-TYPE
    SYNTAX       SnmpAdminString
    MAX-ACCESS   read-only
    STATUS       current
    DESCRIPTION
        "Cisco UCS lstorage:ProfileBinding:rn managed object property"
    ::= { cucsLstorageProfileBindingEntry 3 }

cucsLstorageProfileBindingIssues OBJECT-TYPE
    SYNTAX       CucsLsConfigIssues
    MAX-ACCESS   read-only
    STATUS       current
    DESCRIPTION
        "Cisco UCS lstorage:ProfileBinding:issues managed object property"
    ::= { cucsLstorageProfileBindingEntry 5 }

cucsLstorageProfileBindingName OBJECT-TYPE
    SYNTAX       SnmpAdminString
    MAX-ACCESS   read-only
    STATUS       current
    DESCRIPTION
        "Cisco UCS lstorage:ProfileBinding:name managed object property"
    ::= { cucsLstorageProfileBindingEntry 6 }

cucsLstorageProfileBindingOperStorageProfileName OBJECT-TYPE
    SYNTAX       SnmpAdminString
    MAX-ACCESS   read-only
    STATUS       current
    DESCRIPTION
        "Cisco UCS lstorage:ProfileBinding:operStorageProfileName
        managed object property"
    ::= { cucsLstorageProfileBindingEntry 7 }

cucsLstorageProfileBindingStorageProfileName OBJECT-TYPE
    SYNTAX       SnmpAdminString
    MAX-ACCESS   read-only
    STATUS       current
    DESCRIPTION
        "Cisco UCS lstorage:ProfileBinding:storageProfileName
        managed object property"
    ::= { cucsLstorageProfileBindingEntry 8 }

cucsLstorageProfileDefTable OBJECT-TYPE
    SYNTAX           SEQUENCE OF CucsLstorageProfileDefEntry
    MAX-ACCESS       not-accessible
    STATUS           current
    DESCRIPTION
        "Cisco UCS lstorage:ProfileDef managed object table"
    ::= { cucsLstorageObjects 39 }

cucsLstorageProfileDefEntry OBJECT-TYPE
    SYNTAX           CucsLstorageProfileDefEntry
    MAX-ACCESS       not-accessible
    STATUS           current
    DESCRIPTION
        "Entry for the cucsLstorageProfileDefTable table."
    INDEX { cucsLstorageProfileDefInstanceId }
    ::= { cucsLstorageProfileDefTable 1 }

CucsLstorageProfileDefEntry ::= SEQUENCE {
    cucsLstorageProfileDefInstanceId                                 CucsManagedObjectId,
    cucsLstorageProfileDefDn                                         CucsManagedObjectDn,
    cucsLstorageProfileDefRn                                         SnmpAdminString,
    cucsLstorageProfileDefAssignedToDn                               SnmpAdminString,
    cucsLstorageProfileDefAvailability                               CucsLstorageAvailability,
    cucsLstorageProfileDefDescr                                      SnmpAdminString,
    cucsLstorageProfileDefIntId                                      SnmpAdminString,
    cucsLstorageProfileDefName                                       SnmpAdminString,
    cucsLstorageProfileDefPolicyLevel                                Gauge32,
    cucsLstorageProfileDefPolicyOwner                                CucsPolicyPolicyOwner
}

cucsLstorageProfileDefInstanceId OBJECT-TYPE
    SYNTAX       CucsManagedObjectId
    MAX-ACCESS   not-accessible
    STATUS       current
    DESCRIPTION
        "Instance identifier of the managed object."
    ::= { cucsLstorageProfileDefEntry 1 }

cucsLstorageProfileDefDn OBJECT-TYPE
    SYNTAX       CucsManagedObjectDn
    MAX-ACCESS   read-only
    STATUS       current
    DESCRIPTION
        "Cisco UCS lstorage:ProfileDef:dn managed object property"
    ::= { cucsLstorageProfileDefEntry 2 }

cucsLstorageProfileDefRn OBJECT-TYPE
    SYNTAX       SnmpAdminString
    MAX-ACCESS   read-only
    STATUS       current
    DESCRIPTION
        "Cisco UCS lstorage:ProfileDef:rn managed object property"
    ::= { cucsLstorageProfileDefEntry 3 }

cucsLstorageProfileDefAssignedToDn OBJECT-TYPE
    SYNTAX       SnmpAdminString
    MAX-ACCESS   read-only
    STATUS       current
    DESCRIPTION
        "Cisco UCS lstorage:ProfileDef:assignedToDn managed
        object property"
    ::= { cucsLstorageProfileDefEntry 4 }

cucsLstorageProfileDefAvailability OBJECT-TYPE
    SYNTAX       CucsLstorageAvailability
    MAX-ACCESS   read-only
    STATUS       current
    DESCRIPTION
        "Cisco UCS lstorage:ProfileDef:availability managed
        object property"
    ::= { cucsLstorageProfileDefEntry 5 }

cucsLstorageProfileDefDescr OBJECT-TYPE
    SYNTAX       SnmpAdminString
    MAX-ACCESS   read-only
    STATUS       current
    DESCRIPTION
        "Cisco UCS lstorage:ProfileDef:descr managed object property"
    ::= { cucsLstorageProfileDefEntry 6 }

cucsLstorageProfileDefIntId OBJECT-TYPE
    SYNTAX       SnmpAdminString
    MAX-ACCESS   read-only
    STATUS       current
    DESCRIPTION
        "Cisco UCS lstorage:ProfileDef:intId managed object property"
    ::= { cucsLstorageProfileDefEntry 7 }

cucsLstorageProfileDefName OBJECT-TYPE
    SYNTAX       SnmpAdminString
    MAX-ACCESS   read-only
    STATUS       current
    DESCRIPTION
        "Cisco UCS lstorage:ProfileDef:name managed object property"
    ::= { cucsLstorageProfileDefEntry 8 }

cucsLstorageProfileDefPolicyLevel OBJECT-TYPE
    SYNTAX       Gauge32
    MAX-ACCESS   read-only
    STATUS       current
    DESCRIPTION
        "Cisco UCS lstorage:ProfileDef:policyLevel managed
        object property"
    ::= { cucsLstorageProfileDefEntry 9 }

cucsLstorageProfileDefPolicyOwner OBJECT-TYPE
    SYNTAX       CucsPolicyPolicyOwner
    MAX-ACCESS   read-only
    STATUS       current
    DESCRIPTION
        "Cisco UCS lstorage:ProfileDef:policyOwner managed
        object property"
    ::= { cucsLstorageProfileDefEntry 10 }

cucsLstorageVirtualDriveDefTable OBJECT-TYPE
    SYNTAX           SEQUENCE OF CucsLstorageVirtualDriveDefEntry
    MAX-ACCESS       not-accessible
    STATUS           current
    DESCRIPTION
        "Cisco UCS lstorage:VirtualDriveDef managed object table"
    ::= { cucsLstorageObjects 49 }

cucsLstorageVirtualDriveDefEntry OBJECT-TYPE
    SYNTAX           CucsLstorageVirtualDriveDefEntry
    MAX-ACCESS       not-accessible
    STATUS           current
    DESCRIPTION
        "Entry for the cucsLstorageVirtualDriveDefTable table."
    INDEX { cucsLstorageVirtualDriveDefInstanceId }
    ::= { cucsLstorageVirtualDriveDefTable 1 }

CucsLstorageVirtualDriveDefEntry ::= SEQUENCE {
    cucsLstorageVirtualDriveDefInstanceId                            CucsManagedObjectId,
    cucsLstorageVirtualDriveDefDn                                    CucsManagedObjectDn,
    cucsLstorageVirtualDriveDefRn                                    SnmpAdminString,
    cucsLstorageVirtualDriveDefAccessPolicy                          CucsLstorageVirtualDriveDefAccessPolicy,
    cucsLstorageVirtualDriveDefDriveCache                            CucsLstorageVirtualDriveDefDriveCache,
    cucsLstorageVirtualDriveDefIoPolicy                              CucsLstorageVirtualDriveDefIoPolicy,
    cucsLstorageVirtualDriveDefReadPolicy                            CucsLstorageVirtualDriveDefReadPolicy,
    cucsLstorageVirtualDriveDefStripSize                             CucsLstorageVirtualDriveDefStripSize,
    cucsLstorageVirtualDriveDefWriteCachePolicy                      CucsLstorageVirtualDriveDefWriteCachePolicy
}

cucsLstorageVirtualDriveDefInstanceId OBJECT-TYPE
    SYNTAX       CucsManagedObjectId
    MAX-ACCESS   not-accessible
    STATUS       current
    DESCRIPTION
        "Instance identifier of the managed object."
    ::= { cucsLstorageVirtualDriveDefEntry 1 }

cucsLstorageVirtualDriveDefDn OBJECT-TYPE
    SYNTAX       CucsManagedObjectDn
    MAX-ACCESS   read-only
    STATUS       current
    DESCRIPTION
        "Cisco UCS lstorage:VirtualDriveDef:dn managed object property"
    ::= { cucsLstorageVirtualDriveDefEntry 2 }

cucsLstorageVirtualDriveDefRn OBJECT-TYPE
    SYNTAX       SnmpAdminString
    MAX-ACCESS   read-only
    STATUS       current
    DESCRIPTION
        "Cisco UCS lstorage:VirtualDriveDef:rn managed object property"
    ::= { cucsLstorageVirtualDriveDefEntry 3 }

cucsLstorageVirtualDriveDefAccessPolicy OBJECT-TYPE
    SYNTAX       CucsLstorageVirtualDriveDefAccessPolicy
    MAX-ACCESS   read-only
    STATUS       current
    DESCRIPTION
        "Cisco UCS lstorage:VirtualDriveDef:accessPolicy
        managed object property"
    ::= { cucsLstorageVirtualDriveDefEntry 4 }

cucsLstorageVirtualDriveDefDriveCache OBJECT-TYPE
    SYNTAX       CucsLstorageVirtualDriveDefDriveCache
    MAX-ACCESS   read-only
    STATUS       current
    DESCRIPTION
        "Cisco UCS lstorage:VirtualDriveDef:driveCache
        managed object property"
    ::= { cucsLstorageVirtualDriveDefEntry 5 }

cucsLstorageVirtualDriveDefIoPolicy OBJECT-TYPE
    SYNTAX       CucsLstorageVirtualDriveDefIoPolicy
    MAX-ACCESS   read-only
    STATUS       current
    DESCRIPTION
        "Cisco UCS lstorage:VirtualDriveDef:ioPolicy managed
        object property"
    ::= { cucsLstorageVirtualDriveDefEntry 6 }

cucsLstorageVirtualDriveDefReadPolicy OBJECT-TYPE
    SYNTAX       CucsLstorageVirtualDriveDefReadPolicy
    MAX-ACCESS   read-only
    STATUS       current
    DESCRIPTION
        "Cisco UCS lstorage:VirtualDriveDef:readPolicy
        managed object property"
    ::= { cucsLstorageVirtualDriveDefEntry 7 }

cucsLstorageVirtualDriveDefStripSize OBJECT-TYPE
    SYNTAX       CucsLstorageVirtualDriveDefStripSize
    MAX-ACCESS   read-only
    STATUS       current
    DESCRIPTION
        "Cisco UCS lstorage:VirtualDriveDef:stripSize managed
        object property"
    ::= { cucsLstorageVirtualDriveDefEntry 8 }

cucsLstorageVirtualDriveDefWriteCachePolicy OBJECT-TYPE
    SYNTAX       CucsLstorageVirtualDriveDefWriteCachePolicy
    MAX-ACCESS   read-only
    STATUS       current
    DESCRIPTION
        "Cisco UCS lstorage:VirtualDriveDef:writeCachePolicy
        managed object property"
    ::= { cucsLstorageVirtualDriveDefEntry 9 }

END
