-- *********************************************************************
-- CISCO-UNIFIED-COMPUTING-NETWORK-MIB.my
-- 
-- MIB representation of the Cisco Unified Computing System
-- NETWORK management information model package
-- 
-- Created June 2015 by Charles Bullis
-- 
-- Copyright (c) 2005-2015 Cisco Systems, Inc. All rights reserved.
-- 
-- *********************************************************************

CISCO-UNIFIED-COMPUTING-NETWORK-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsEquipmentSensorThresholdStatus,
    CucsMgmtAdminState,
    CucsNetworkElementOperability,
    CucsNetworkIfStatsType,
    CucsNetworkIfStatsUnits,
    CucsNetworkInventoryStatus,
    CucsNetworkSwitchId,
    CucsNetworkVlanCountStatus
        FROM CISCO-UNIFIED-COMPUTING-TC-MIB;

cucsNetworkObjects MODULE-IDENTITY
    LAST-UPDATED    "201506290000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        NETWORK management information model package"
    ::= { ciscoUnifiedComputingMIBObjects 32 }

cucsNetworkElementTable OBJECT-TYPE
    SYNTAX           SEQUENCE OF CucsNetworkElementEntry
    MAX-ACCESS       not-accessible
    STATUS           current
    DESCRIPTION
        "Cisco UCS network:Element managed object table"
    ::= { cucsNetworkObjects 1 }

cucsNetworkElementEntry OBJECT-TYPE
    SYNTAX           CucsNetworkElementEntry
    MAX-ACCESS       not-accessible
    STATUS           current
    DESCRIPTION
        "Entry for the cucsNetworkElementTable table."
    INDEX { cucsNetworkElementInstanceId }
    ::= { cucsNetworkElementTable 1 }

CucsNetworkElementEntry ::= SEQUENCE {
    cucsNetworkElementInstanceId                                     CucsManagedObjectId,
    cucsNetworkElementDn                                             CucsManagedObjectDn,
    cucsNetworkElementRn                                             SnmpAdminString,
    cucsNetworkElementAdminInbandIfState                             CucsMgmtAdminState,
    cucsNetworkElementFltAggr                                        Unsigned64,
    cucsNetworkElementId                                             CucsNetworkSwitchId,
    cucsNetworkElementInbandIfGw                                     InetAddressIPv4,
    cucsNetworkElementInbandIfIp                                     InetAddressIPv4,
    cucsNetworkElementInbandIfMask                                   InetAddressIPv4,
    cucsNetworkElementInbandIfVnet                                   Gauge32,
    cucsNetworkElementModel                                          SnmpAdminString,
    cucsNetworkElementOobIfGw                                        InetAddressIPv4,
    cucsNetworkElementOobIfIp                                        InetAddressIPv4,
    cucsNetworkElementOobIfMask                                      InetAddressIPv4,
    cucsNetworkElementOperability                                    CucsNetworkElementOperability,
    cucsNetworkElementRevision                                       SnmpAdminString,
    cucsNetworkElementSerial                                         SnmpAdminString,
    cucsNetworkElementTotalMemory                                    Gauge32,
    cucsNetworkElementVendor                                         SnmpAdminString,
    cucsNetworkElementInventoryStatus                                CucsNetworkInventoryStatus,
    cucsNetworkElementThermal                                        CucsEquipmentSensorThresholdStatus,
    cucsNetworkElementDiffMemory                                     Gauge32,
    cucsNetworkElementExpectedMemory                                 Gauge32
}

cucsNetworkElementInstanceId OBJECT-TYPE
    SYNTAX       CucsManagedObjectId
    MAX-ACCESS   not-accessible
    STATUS       current
    DESCRIPTION
        "Instance identifier of the managed object."
    ::= { cucsNetworkElementEntry 1 }

cucsNetworkElementDn OBJECT-TYPE
    SYNTAX       CucsManagedObjectDn
    MAX-ACCESS   read-only
    STATUS       current
    DESCRIPTION
        "Cisco UCS network:Element:dn managed object property"
    ::= { cucsNetworkElementEntry 2 }

cucsNetworkElementRn OBJECT-TYPE
    SYNTAX       SnmpAdminString
    MAX-ACCESS   read-only
    STATUS       current
    DESCRIPTION
        "Cisco UCS network:Element:rn managed object property"
    ::= { cucsNetworkElementEntry 3 }

cucsNetworkElementAdminInbandIfState OBJECT-TYPE
    SYNTAX       CucsMgmtAdminState
    MAX-ACCESS   read-only
    STATUS       current
    DESCRIPTION
        "Cisco UCS network:Element:adminInbandIfState managed
        object property"
    ::= { cucsNetworkElementEntry 4 }

cucsNetworkElementFltAggr OBJECT-TYPE
    SYNTAX       Unsigned64
    MAX-ACCESS   read-only
    STATUS       current
    DESCRIPTION
        "Cisco UCS network:Element:fltAggr managed object property"
    ::= { cucsNetworkElementEntry 5 }

cucsNetworkElementId OBJECT-TYPE
    SYNTAX       CucsNetworkSwitchId
    MAX-ACCESS   read-only
    STATUS       current
    DESCRIPTION
        "Cisco UCS network:Element:id managed object property"
    ::= { cucsNetworkElementEntry 6 }

cucsNetworkElementInbandIfGw OBJECT-TYPE
    SYNTAX       InetAddressIPv4
    MAX-ACCESS   read-only
    STATUS       current
    DESCRIPTION
        "Cisco UCS network:Element:inbandIfGw managed object property"
    ::= { cucsNetworkElementEntry 7 }

cucsNetworkElementInbandIfIp OBJECT-TYPE
    SYNTAX       InetAddressIPv4
    MAX-ACCESS   read-only
    STATUS       current
    DESCRIPTION
        "Cisco UCS network:Element:inbandIfIp managed object property"
    ::= { cucsNetworkElementEntry 8 }

cucsNetworkElementInbandIfMask OBJECT-TYPE
    SYNTAX       InetAddressIPv4
    MAX-ACCESS   read-only
    STATUS       current
    DESCRIPTION
        "Cisco UCS network:Element:inbandIfMask managed object property"
    ::= { cucsNetworkElementEntry 9 }

cucsNetworkElementInbandIfVnet OBJECT-TYPE
    SYNTAX       Gauge32
    MAX-ACCESS   read-only
    STATUS       current
    DESCRIPTION
        "Cisco UCS network:Element:inbandIfVnet managed object property"
    ::= { cucsNetworkElementEntry 10 }

cucsNetworkElementModel OBJECT-TYPE
    SYNTAX       SnmpAdminString
    MAX-ACCESS   read-only
    STATUS       current
    DESCRIPTION
        "Cisco UCS network:Element:model managed object property"
    ::= { cucsNetworkElementEntry 11 }

cucsNetworkElementOobIfGw OBJECT-TYPE
    SYNTAX       InetAddressIPv4
    MAX-ACCESS   read-only
    STATUS       current
    DESCRIPTION
        "Cisco UCS network:Element:oobIfGw managed object property"
    ::= { cucsNetworkElementEntry 12 }

cucsNetworkElementOobIfIp OBJECT-TYPE
    SYNTAX       InetAddressIPv4
    MAX-ACCESS   read-only
    STATUS       current
    DESCRIPTION
        "Cisco UCS network:Element:oobIfIp managed object property"
    ::= { cucsNetworkElementEntry 13 }

cucsNetworkElementOobIfMask OBJECT-TYPE
    SYNTAX       InetAddressIPv4
    MAX-ACCESS   read-only
    STATUS       current
    DESCRIPTION
        "Cisco UCS network:Element:oobIfMask managed object property"
    ::= { cucsNetworkElementEntry 14 }

cucsNetworkElementOperability OBJECT-TYPE
    SYNTAX       CucsNetworkElementOperability
    MAX-ACCESS   read-only
    STATUS       current
    DESCRIPTION
        "Cisco UCS network:Element:operability managed object property"
    ::= { cucsNetworkElementEntry 15 }

cucsNetworkElementRevision OBJECT-TYPE
    SYNTAX       SnmpAdminString
    MAX-ACCESS   read-only
    STATUS       current
    DESCRIPTION
        "Cisco UCS network:Element:revision managed object property"
    ::= { cucsNetworkElementEntry 16 }

cucsNetworkElementSerial OBJECT-TYPE
    SYNTAX       SnmpAdminString
    MAX-ACCESS   read-only
    STATUS       current
    DESCRIPTION
        "Cisco UCS network:Element:serial managed object property"
    ::= { cucsNetworkElementEntry 17 }

cucsNetworkElementTotalMemory OBJECT-TYPE
    SYNTAX       Gauge32
    MAX-ACCESS   read-only
    STATUS       current
    DESCRIPTION
        "Cisco UCS network:Element:totalMemory managed object property"
    ::= { cucsNetworkElementEntry 18 }

cucsNetworkElementVendor OBJECT-TYPE
    SYNTAX       SnmpAdminString
    MAX-ACCESS   read-only
    STATUS       current
    DESCRIPTION
        "Cisco UCS network:Element:vendor managed object property"
    ::= { cucsNetworkElementEntry 19 }

cucsNetworkElementInventoryStatus OBJECT-TYPE
    SYNTAX       CucsNetworkInventoryStatus
    MAX-ACCESS   read-only
    STATUS       current
    DESCRIPTION
        "Cisco UCS network:Element:inventoryStatus managed
        object property"
    ::= { cucsNetworkElementEntry 20 }

cucsNetworkElementThermal OBJECT-TYPE
    SYNTAX       CucsEquipmentSensorThresholdStatus
    MAX-ACCESS   read-only
    STATUS       current
    DESCRIPTION
        "Cisco UCS network:Element:thermal managed object property"
    ::= { cucsNetworkElementEntry 21 }

cucsNetworkElementDiffMemory OBJECT-TYPE
    SYNTAX       Gauge32
    MAX-ACCESS   read-only
    STATUS       current
    DESCRIPTION
        "Cisco UCS network:Element:diffMemory managed object property"
    ::= { cucsNetworkElementEntry 22 }

cucsNetworkElementExpectedMemory OBJECT-TYPE
    SYNTAX       Gauge32
    MAX-ACCESS   read-only
    STATUS       current
    DESCRIPTION
        "Cisco UCS network:Element:expectedMemory managed object property"
    ::= { cucsNetworkElementEntry 23 }

cucsNetworkIfStatsTable OBJECT-TYPE
    SYNTAX           SEQUENCE OF CucsNetworkIfStatsEntry
    MAX-ACCESS       not-accessible
    STATUS           current
    DESCRIPTION
        "Cisco UCS network:IfStats managed object table"
    ::= { cucsNetworkObjects 2 }

cucsNetworkIfStatsEntry OBJECT-TYPE
    SYNTAX           CucsNetworkIfStatsEntry
    MAX-ACCESS       not-accessible
    STATUS           current
    DESCRIPTION
        "Entry for the cucsNetworkIfStatsTable table."
    INDEX { cucsNetworkIfStatsInstanceId }
    ::= { cucsNetworkIfStatsTable 1 }

CucsNetworkIfStatsEntry ::= SEQUENCE {
    cucsNetworkIfStatsInstanceId                                     CucsManagedObjectId,
    cucsNetworkIfStatsDn                                             CucsManagedObjectDn,
    cucsNetworkIfStatsRn                                             SnmpAdminString,
    cucsNetworkIfStatsIn                                             Unsigned64,
    cucsNetworkIfStatsOut                                            Unsigned64,
    cucsNetworkIfStatsType                                           CucsNetworkIfStatsType,
    cucsNetworkIfStatsUnits                                          CucsNetworkIfStatsUnits
}

cucsNetworkIfStatsInstanceId OBJECT-TYPE
    SYNTAX       CucsManagedObjectId
    MAX-ACCESS   not-accessible
    STATUS       current
    DESCRIPTION
        "Instance identifier of the managed object."
    ::= { cucsNetworkIfStatsEntry 1 }

cucsNetworkIfStatsDn OBJECT-TYPE
    SYNTAX       CucsManagedObjectDn
    MAX-ACCESS   read-only
    STATUS       current
    DESCRIPTION
        "Cisco UCS network:IfStats:dn managed object property"
    ::= { cucsNetworkIfStatsEntry 2 }

cucsNetworkIfStatsRn OBJECT-TYPE
    SYNTAX       SnmpAdminString
    MAX-ACCESS   read-only
    STATUS       current
    DESCRIPTION
        "Cisco UCS network:IfStats:rn managed object property"
    ::= { cucsNetworkIfStatsEntry 3 }

cucsNetworkIfStatsIn OBJECT-TYPE
    SYNTAX       Unsigned64
    MAX-ACCESS   read-only
    STATUS       current
    DESCRIPTION
        "Cisco UCS network:IfStats:in managed object property"
    ::= { cucsNetworkIfStatsEntry 4 }

cucsNetworkIfStatsOut OBJECT-TYPE
    SYNTAX       Unsigned64
    MAX-ACCESS   read-only
    STATUS       current
    DESCRIPTION
        "Cisco UCS network:IfStats:out managed object property"
    ::= { cucsNetworkIfStatsEntry 5 }

cucsNetworkIfStatsType OBJECT-TYPE
    SYNTAX       CucsNetworkIfStatsType
    MAX-ACCESS   read-only
    STATUS       current
    DESCRIPTION
        "Cisco UCS network:IfStats:type managed object property"
    ::= { cucsNetworkIfStatsEntry 6 }

cucsNetworkIfStatsUnits OBJECT-TYPE
    SYNTAX       CucsNetworkIfStatsUnits
    MAX-ACCESS   read-only
    STATUS       current
    DESCRIPTION
        "Cisco UCS network:IfStats:units managed object property"
    ::= { cucsNetworkIfStatsEntry 7 }

cucsNetworkLanNeighborEntryTable OBJECT-TYPE
    SYNTAX           SEQUENCE OF CucsNetworkLanNeighborEntryEntry
    MAX-ACCESS       not-accessible
    STATUS           current
    DESCRIPTION
        "Cisco UCS network:LanNeighborEntry managed object table"
    ::= { cucsNetworkObjects 4 }

cucsNetworkLanNeighborEntryEntry OBJECT-TYPE
    SYNTAX           CucsNetworkLanNeighborEntryEntry
    MAX-ACCESS       not-accessible
    STATUS           current
    DESCRIPTION
        "Entry for the cucsNetworkLanNeighborEntryTable table."
    INDEX { cucsNetworkLanNeighborEntryInstanceId }
    ::= { cucsNetworkLanNeighborEntryTable 1 }

CucsNetworkLanNeighborEntryEntry ::= SEQUENCE {
    cucsNetworkLanNeighborEntryInstanceId                            CucsManagedObjectId,
    cucsNetworkLanNeighborEntryDn                                    CucsManagedObjectDn,
    cucsNetworkLanNeighborEntryRn                                    SnmpAdminString,
    cucsNetworkLanNeighborEntryCapabilities                          SnmpAdminString,
    cucsNetworkLanNeighborEntryDeviceId                              SnmpAdminString,
    cucsNetworkLanNeighborEntryFiPortDn                              SnmpAdminString,
    cucsNetworkLanNeighborEntryIpV4Address                           SnmpAdminString,
    cucsNetworkLanNeighborEntryIpV4MgmtAddress                       SnmpAdminString,
    cucsNetworkLanNeighborEntryLocalInterface                        SnmpAdminString,
    cucsNetworkLanNeighborEntryNativeVlan                            Gauge32,
    cucsNetworkLanNeighborEntryPlatform                              SnmpAdminString,
    cucsNetworkLanNeighborEntryRemoteInterface                       SnmpAdminString
}

cucsNetworkLanNeighborEntryInstanceId OBJECT-TYPE
    SYNTAX       CucsManagedObjectId
    MAX-ACCESS   not-accessible
    STATUS       current
    DESCRIPTION
        "Instance identifier of the managed object."
    ::= { cucsNetworkLanNeighborEntryEntry 1 }

cucsNetworkLanNeighborEntryDn OBJECT-TYPE
    SYNTAX       CucsManagedObjectDn
    MAX-ACCESS   read-only
    STATUS       current
    DESCRIPTION
        "Cisco UCS network:LanNeighborEntry:dn managed object property"
    ::= { cucsNetworkLanNeighborEntryEntry 2 }

cucsNetworkLanNeighborEntryRn OBJECT-TYPE
    SYNTAX       SnmpAdminString
    MAX-ACCESS   read-only
    STATUS       current
    DESCRIPTION
        "Cisco UCS network:LanNeighborEntry:rn managed object property"
    ::= { cucsNetworkLanNeighborEntryEntry 3 }

cucsNetworkLanNeighborEntryCapabilities OBJECT-TYPE
    SYNTAX       SnmpAdminString
    MAX-ACCESS   read-only
    STATUS       current
    DESCRIPTION
        "Cisco UCS network:LanNeighborEntry:capabilities
        managed object property"
    ::= { cucsNetworkLanNeighborEntryEntry 4 }

cucsNetworkLanNeighborEntryDeviceId OBJECT-TYPE
    SYNTAX       SnmpAdminString
    MAX-ACCESS   read-only
    STATUS       current
    DESCRIPTION
        "Cisco UCS network:LanNeighborEntry:deviceId managed
        object property"
    ::= { cucsNetworkLanNeighborEntryEntry 5 }

cucsNetworkLanNeighborEntryFiPortDn OBJECT-TYPE
    SYNTAX       SnmpAdminString
    MAX-ACCESS   read-only
    STATUS       current
    DESCRIPTION
        "Cisco UCS network:LanNeighborEntry:fiPortDn managed
        object property"
    ::= { cucsNetworkLanNeighborEntryEntry 6 }

cucsNetworkLanNeighborEntryIpV4Address OBJECT-TYPE
    SYNTAX       SnmpAdminString
    MAX-ACCESS   read-only
    STATUS       current
    DESCRIPTION
        "Cisco UCS network:LanNeighborEntry:ipV4Address
        managed object property"
    ::= { cucsNetworkLanNeighborEntryEntry 7 }

cucsNetworkLanNeighborEntryIpV4MgmtAddress OBJECT-TYPE
    SYNTAX       SnmpAdminString
    MAX-ACCESS   read-only
    STATUS       current
    DESCRIPTION
        "Cisco UCS network:LanNeighborEntry:ipV4MgmtAddress
        managed object property"
    ::= { cucsNetworkLanNeighborEntryEntry 8 }

cucsNetworkLanNeighborEntryLocalInterface OBJECT-TYPE
    SYNTAX       SnmpAdminString
    MAX-ACCESS   read-only
    STATUS       current
    DESCRIPTION
        "Cisco UCS network:LanNeighborEntry:localInterface
        managed object property"
    ::= { cucsNetworkLanNeighborEntryEntry 9 }

cucsNetworkLanNeighborEntryNativeVlan OBJECT-TYPE
    SYNTAX       Gauge32
    MAX-ACCESS   read-only
    STATUS       current
    DESCRIPTION
        "Cisco UCS network:LanNeighborEntry:nativeVlan
        managed object property"
    ::= { cucsNetworkLanNeighborEntryEntry 10 }

cucsNetworkLanNeighborEntryPlatform OBJECT-TYPE
    SYNTAX       SnmpAdminString
    MAX-ACCESS   read-only
    STATUS       current
    DESCRIPTION
        "Cisco UCS network:LanNeighborEntry:platform managed
        object property"
    ::= { cucsNetworkLanNeighborEntryEntry 11 }

cucsNetworkLanNeighborEntryRemoteInterface OBJECT-TYPE
    SYNTAX       SnmpAdminString
    MAX-ACCESS   read-only
    STATUS       current
    DESCRIPTION
        "Cisco UCS network:LanNeighborEntry:remoteInterface
        managed object property"
    ::= { cucsNetworkLanNeighborEntryEntry 12 }

cucsNetworkLanNeighborsTable OBJECT-TYPE
    SYNTAX           SEQUENCE OF CucsNetworkLanNeighborsEntry
    MAX-ACCESS       not-accessible
    STATUS           current
    DESCRIPTION
        "Cisco UCS network:LanNeighbors managed object table"
    ::= { cucsNetworkObjects 5 }

cucsNetworkLanNeighborsEntry OBJECT-TYPE
    SYNTAX           CucsNetworkLanNeighborsEntry
    MAX-ACCESS       not-accessible
    STATUS           current
    DESCRIPTION
        "Entry for the cucsNetworkLanNeighborsTable table."
    INDEX { cucsNetworkLanNeighborsInstanceId }
    ::= { cucsNetworkLanNeighborsTable 1 }

CucsNetworkLanNeighborsEntry ::= SEQUENCE {
    cucsNetworkLanNeighborsInstanceId                                CucsManagedObjectId,
    cucsNetworkLanNeighborsDn                                        CucsManagedObjectDn,
    cucsNetworkLanNeighborsRn                                        SnmpAdminString
}

cucsNetworkLanNeighborsInstanceId OBJECT-TYPE
    SYNTAX       CucsManagedObjectId
    MAX-ACCESS   not-accessible
    STATUS       current
    DESCRIPTION
        "Instance identifier of the managed object."
    ::= { cucsNetworkLanNeighborsEntry 1 }

cucsNetworkLanNeighborsDn OBJECT-TYPE
    SYNTAX       CucsManagedObjectDn
    MAX-ACCESS   read-only
    STATUS       current
    DESCRIPTION
        "Cisco UCS network:LanNeighbors:dn managed object property"
    ::= { cucsNetworkLanNeighborsEntry 2 }

cucsNetworkLanNeighborsRn OBJECT-TYPE
    SYNTAX       SnmpAdminString
    MAX-ACCESS   read-only
    STATUS       current
    DESCRIPTION
        "Cisco UCS network:LanNeighbors:rn managed object property"
    ::= { cucsNetworkLanNeighborsEntry 3 }

cucsNetworkOperLevelTable OBJECT-TYPE
    SYNTAX           SEQUENCE OF CucsNetworkOperLevelEntry
    MAX-ACCESS       not-accessible
    STATUS           current
    DESCRIPTION
        "Cisco UCS network:OperLevel managed object table"
    ::= { cucsNetworkObjects 3 }

cucsNetworkOperLevelEntry OBJECT-TYPE
    SYNTAX           CucsNetworkOperLevelEntry
    MAX-ACCESS       not-accessible
    STATUS           current
    DESCRIPTION
        "Entry for the cucsNetworkOperLevelTable table."
    INDEX { cucsNetworkOperLevelInstanceId }
    ::= { cucsNetworkOperLevelTable 1 }

CucsNetworkOperLevelEntry ::= SEQUENCE {
    cucsNetworkOperLevelInstanceId                                   CucsManagedObjectId,
    cucsNetworkOperLevelDn                                           CucsManagedObjectDn,
    cucsNetworkOperLevelRn                                           SnmpAdminString,
    cucsNetworkOperLevelId                                           CucsNetworkSwitchId,
    cucsNetworkOperLevelMaxPrimaryVlanCount                          Gauge32,
    cucsNetworkOperLevelPrimaryVlanCount                             Gauge32,
    cucsNetworkOperLevelPrimaryVlanCountStatus                       CucsNetworkVlanCountStatus,
    cucsNetworkOperLevelMaxSecVlanPerPrimaryVlanCount                Gauge32,
    cucsNetworkOperLevelMaxSecondaryVlanCount                        Gauge32,
    cucsNetworkOperLevelSecondaryVlanCount                           Gauge32,
    cucsNetworkOperLevelSecondaryVlanCountStatus                     CucsNetworkVlanCountStatus
}

cucsNetworkOperLevelInstanceId OBJECT-TYPE
    SYNTAX       CucsManagedObjectId
    MAX-ACCESS   not-accessible
    STATUS       current
    DESCRIPTION
        "Instance identifier of the managed object."
    ::= { cucsNetworkOperLevelEntry 1 }

cucsNetworkOperLevelDn OBJECT-TYPE
    SYNTAX       CucsManagedObjectDn
    MAX-ACCESS   read-only
    STATUS       current
    DESCRIPTION
        "Cisco UCS network:OperLevel:dn managed object property"
    ::= { cucsNetworkOperLevelEntry 2 }

cucsNetworkOperLevelRn OBJECT-TYPE
    SYNTAX       SnmpAdminString
    MAX-ACCESS   read-only
    STATUS       current
    DESCRIPTION
        "Cisco UCS network:OperLevel:rn managed object property"
    ::= { cucsNetworkOperLevelEntry 3 }

cucsNetworkOperLevelId OBJECT-TYPE
    SYNTAX       CucsNetworkSwitchId
    MAX-ACCESS   read-only
    STATUS       current
    DESCRIPTION
        "Cisco UCS network:OperLevel:id managed object property"
    ::= { cucsNetworkOperLevelEntry 4 }

cucsNetworkOperLevelMaxPrimaryVlanCount OBJECT-TYPE
    SYNTAX       Gauge32
    MAX-ACCESS   read-only
    STATUS       current
    DESCRIPTION
        "Cisco UCS network:OperLevel:maxPrimaryVlanCount
        managed object property"
    ::= { cucsNetworkOperLevelEntry 8 }

cucsNetworkOperLevelPrimaryVlanCount OBJECT-TYPE
    SYNTAX       Gauge32
    MAX-ACCESS   read-only
    STATUS       current
    DESCRIPTION
        "Cisco UCS network:OperLevel:primaryVlanCount managed
        object property"
    ::= { cucsNetworkOperLevelEntry 9 }

cucsNetworkOperLevelPrimaryVlanCountStatus OBJECT-TYPE
    SYNTAX       CucsNetworkVlanCountStatus
    MAX-ACCESS   read-only
    STATUS       current
    DESCRIPTION
        "Cisco UCS network:OperLevel:primaryVlanCountStatus
        managed object property"
    ::= { cucsNetworkOperLevelEntry 10 }

cucsNetworkOperLevelMaxSecVlanPerPrimaryVlanCount OBJECT-TYPE
    SYNTAX       Gauge32
    MAX-ACCESS   read-only
    STATUS       current
    DESCRIPTION
        "Cisco UCS network:OperLevel:maxSecVlanPerPrimaryVlanCount
        managed object property"
    ::= { cucsNetworkOperLevelEntry 11 }

cucsNetworkOperLevelMaxSecondaryVlanCount OBJECT-TYPE
    SYNTAX       Gauge32
    MAX-ACCESS   read-only
    STATUS       current
    DESCRIPTION
        "Cisco UCS network:OperLevel:maxSecondaryVlanCount
        managed object property"
    ::= { cucsNetworkOperLevelEntry 12 }

cucsNetworkOperLevelSecondaryVlanCount OBJECT-TYPE
    SYNTAX       Gauge32
    MAX-ACCESS   read-only
    STATUS       current
    DESCRIPTION
        "Cisco UCS network:OperLevel:secondaryVlanCount
        managed object property"
    ::= { cucsNetworkOperLevelEntry 13 }

cucsNetworkOperLevelSecondaryVlanCountStatus OBJECT-TYPE
    SYNTAX       CucsNetworkVlanCountStatus
    MAX-ACCESS   read-only
    STATUS       current
    DESCRIPTION
        "Cisco UCS network:OperLevel:secondaryVlanCountStatus
        managed object property"
    ::= { cucsNetworkOperLevelEntry 14 }

cucsNetworkSanNeighborEntryTable OBJECT-TYPE
    SYNTAX           SEQUENCE OF CucsNetworkSanNeighborEntryEntry
    MAX-ACCESS       not-accessible
    STATUS           current
    DESCRIPTION
        "Cisco UCS network:SanNeighborEntry managed object table"
    ::= { cucsNetworkObjects 6 }

cucsNetworkSanNeighborEntryEntry OBJECT-TYPE
    SYNTAX           CucsNetworkSanNeighborEntryEntry
    MAX-ACCESS       not-accessible
    STATUS           current
    DESCRIPTION
        "Entry for the cucsNetworkSanNeighborEntryTable table."
    INDEX { cucsNetworkSanNeighborEntryInstanceId }
    ::= { cucsNetworkSanNeighborEntryTable 1 }

CucsNetworkSanNeighborEntryEntry ::= SEQUENCE {
    cucsNetworkSanNeighborEntryInstanceId                            CucsManagedObjectId,
    cucsNetworkSanNeighborEntryDn                                    CucsManagedObjectDn,
    cucsNetworkSanNeighborEntryRn                                    SnmpAdminString,
    cucsNetworkSanNeighborEntryFabricMgmtAddr                        SnmpAdminString,
    cucsNetworkSanNeighborEntryFabricNwwn                            SnmpAdminString,
    cucsNetworkSanNeighborEntryFabricPwwn                            SnmpAdminString,
    cucsNetworkSanNeighborEntryFiPortDn                              SnmpAdminString,
    cucsNetworkSanNeighborEntryLocalInterface                        SnmpAdminString,
    cucsNetworkSanNeighborEntryMyNwwn                                SnmpAdminString,
    cucsNetworkSanNeighborEntryMyPwwn                                SnmpAdminString,
    cucsNetworkSanNeighborEntryPortVsan                              SnmpAdminString
}

cucsNetworkSanNeighborEntryInstanceId OBJECT-TYPE
    SYNTAX       CucsManagedObjectId
    MAX-ACCESS   not-accessible
    STATUS       current
    DESCRIPTION
        "Instance identifier of the managed object."
    ::= { cucsNetworkSanNeighborEntryEntry 1 }

cucsNetworkSanNeighborEntryDn OBJECT-TYPE
    SYNTAX       CucsManagedObjectDn
    MAX-ACCESS   read-only
    STATUS       current
    DESCRIPTION
        "Cisco UCS network:SanNeighborEntry:dn managed object property"
    ::= { cucsNetworkSanNeighborEntryEntry 2 }

cucsNetworkSanNeighborEntryRn OBJECT-TYPE
    SYNTAX       SnmpAdminString
    MAX-ACCESS   read-only
    STATUS       current
    DESCRIPTION
        "Cisco UCS network:SanNeighborEntry:rn managed object property"
    ::= { cucsNetworkSanNeighborEntryEntry 3 }

cucsNetworkSanNeighborEntryFabricMgmtAddr OBJECT-TYPE
    SYNTAX       SnmpAdminString
    MAX-ACCESS   read-only
    STATUS       current
    DESCRIPTION
        "Cisco UCS network:SanNeighborEntry:fabricMgmtAddr
        managed object property"
    ::= { cucsNetworkSanNeighborEntryEntry 4 }

cucsNetworkSanNeighborEntryFabricNwwn OBJECT-TYPE
    SYNTAX       SnmpAdminString
    MAX-ACCESS   read-only
    STATUS       current
    DESCRIPTION
        "Cisco UCS network:SanNeighborEntry:fabricNwwn
        managed object property"
    ::= { cucsNetworkSanNeighborEntryEntry 5 }

cucsNetworkSanNeighborEntryFabricPwwn OBJECT-TYPE
    SYNTAX       SnmpAdminString
    MAX-ACCESS   read-only
    STATUS       current
    DESCRIPTION
        "Cisco UCS network:SanNeighborEntry:fabricPwwn
        managed object property"
    ::= { cucsNetworkSanNeighborEntryEntry 6 }

cucsNetworkSanNeighborEntryFiPortDn OBJECT-TYPE
    SYNTAX       SnmpAdminString
    MAX-ACCESS   read-only
    STATUS       current
    DESCRIPTION
        "Cisco UCS network:SanNeighborEntry:fiPortDn managed
        object property"
    ::= { cucsNetworkSanNeighborEntryEntry 7 }

cucsNetworkSanNeighborEntryLocalInterface OBJECT-TYPE
    SYNTAX       SnmpAdminString
    MAX-ACCESS   read-only
    STATUS       current
    DESCRIPTION
        "Cisco UCS network:SanNeighborEntry:localInterface
        managed object property"
    ::= { cucsNetworkSanNeighborEntryEntry 8 }

cucsNetworkSanNeighborEntryMyNwwn OBJECT-TYPE
    SYNTAX       SnmpAdminString
    MAX-ACCESS   read-only
    STATUS       current
    DESCRIPTION
        "Cisco UCS network:SanNeighborEntry:myNwwn managed
        object property"
    ::= { cucsNetworkSanNeighborEntryEntry 9 }

cucsNetworkSanNeighborEntryMyPwwn OBJECT-TYPE
    SYNTAX       SnmpAdminString
    MAX-ACCESS   read-only
    STATUS       current
    DESCRIPTION
        "Cisco UCS network:SanNeighborEntry:myPwwn managed
        object property"
    ::= { cucsNetworkSanNeighborEntryEntry 10 }

cucsNetworkSanNeighborEntryPortVsan OBJECT-TYPE
    SYNTAX       SnmpAdminString
    MAX-ACCESS   read-only
    STATUS       current
    DESCRIPTION
        "Cisco UCS network:SanNeighborEntry:portVsan managed
        object property"
    ::= { cucsNetworkSanNeighborEntryEntry 11 }

cucsNetworkSanNeighborsTable OBJECT-TYPE
    SYNTAX           SEQUENCE OF CucsNetworkSanNeighborsEntry
    MAX-ACCESS       not-accessible
    STATUS           current
    DESCRIPTION
        "Cisco UCS network:SanNeighbors managed object table"
    ::= { cucsNetworkObjects 7 }

cucsNetworkSanNeighborsEntry OBJECT-TYPE
    SYNTAX           CucsNetworkSanNeighborsEntry
    MAX-ACCESS       not-accessible
    STATUS           current
    DESCRIPTION
        "Entry for the cucsNetworkSanNeighborsTable table."
    INDEX { cucsNetworkSanNeighborsInstanceId }
    ::= { cucsNetworkSanNeighborsTable 1 }

CucsNetworkSanNeighborsEntry ::= SEQUENCE {
    cucsNetworkSanNeighborsInstanceId                                CucsManagedObjectId,
    cucsNetworkSanNeighborsDn                                        CucsManagedObjectDn,
    cucsNetworkSanNeighborsRn                                        SnmpAdminString
}

cucsNetworkSanNeighborsInstanceId OBJECT-TYPE
    SYNTAX       CucsManagedObjectId
    MAX-ACCESS   not-accessible
    STATUS       current
    DESCRIPTION
        "Instance identifier of the managed object."
    ::= { cucsNetworkSanNeighborsEntry 1 }

cucsNetworkSanNeighborsDn OBJECT-TYPE
    SYNTAX       CucsManagedObjectDn
    MAX-ACCESS   read-only
    STATUS       current
    DESCRIPTION
        "Cisco UCS network:SanNeighbors:dn managed object property"
    ::= { cucsNetworkSanNeighborsEntry 2 }

cucsNetworkSanNeighborsRn OBJECT-TYPE
    SYNTAX       SnmpAdminString
    MAX-ACCESS   read-only
    STATUS       current
    DESCRIPTION
        "Cisco UCS network:SanNeighbors:rn managed object property"
    ::= { cucsNetworkSanNeighborsEntry 3 }

END
