-- *********************************************************************
-- CISCO-UNIFIED-COMPUTING-DPSEC-MIB.my
-- 
-- MIB representation of the Cisco Unified Computing System
-- DPSEC management information model package
-- 
-- Created June 2015 by Charles Bullis
-- 
-- Copyright (c) 2005-2015 Cisco Systems, Inc. All rights reserved.
-- 
-- *********************************************************************

CISCO-UNIFIED-COMPUTING-DPSEC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsDpsecForgedTransmit,
    CucsPolicyPolicyOwner
        FROM CISCO-UNIFIED-COMPUTING-TC-MIB;

cucsDpsecObjects MODULE-IDENTITY
    LAST-UPDATED    "201506290000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        DPSEC management information model package"
    ::= { ciscoUnifiedComputingMIBObjects 13 }

cucsDpsecMacTable OBJECT-TYPE
    SYNTAX           SEQUENCE OF CucsDpsecMacEntry
    MAX-ACCESS       not-accessible
    STATUS           current
    DESCRIPTION
        "Cisco UCS dpsec:Mac managed object table"
    ::= { cucsDpsecObjects 1 }

cucsDpsecMacEntry OBJECT-TYPE
    SYNTAX           CucsDpsecMacEntry
    MAX-ACCESS       not-accessible
    STATUS           current
    DESCRIPTION
        "Entry for the cucsDpsecMacTable table."
    INDEX { cucsDpsecMacInstanceId }
    ::= { cucsDpsecMacTable 1 }

CucsDpsecMacEntry ::= SEQUENCE {
    cucsDpsecMacInstanceId                                           CucsManagedObjectId,
    cucsDpsecMacDn                                                   CucsManagedObjectDn,
    cucsDpsecMacRn                                                   SnmpAdminString,
    cucsDpsecMacDescr                                                SnmpAdminString,
    cucsDpsecMacForge                                                CucsDpsecForgedTransmit,
    cucsDpsecMacIntId                                                SnmpAdminString,
    cucsDpsecMacName                                                 SnmpAdminString,
    cucsDpsecMacPolicyLevel                                          Gauge32,
    cucsDpsecMacPolicyOwner                                          CucsPolicyPolicyOwner
}

cucsDpsecMacInstanceId OBJECT-TYPE
    SYNTAX       CucsManagedObjectId
    MAX-ACCESS   not-accessible
    STATUS       current
    DESCRIPTION
        "Instance identifier of the managed object."
    ::= { cucsDpsecMacEntry 1 }

cucsDpsecMacDn OBJECT-TYPE
    SYNTAX       CucsManagedObjectDn
    MAX-ACCESS   read-only
    STATUS       current
    DESCRIPTION
        "Cisco UCS dpsec:Mac:dn managed object property"
    ::= { cucsDpsecMacEntry 2 }

cucsDpsecMacRn OBJECT-TYPE
    SYNTAX       SnmpAdminString
    MAX-ACCESS   read-only
    STATUS       current
    DESCRIPTION
        "Cisco UCS dpsec:Mac:rn managed object property"
    ::= { cucsDpsecMacEntry 3 }

cucsDpsecMacDescr OBJECT-TYPE
    SYNTAX       SnmpAdminString
    MAX-ACCESS   read-only
    STATUS       current
    DESCRIPTION
        "Cisco UCS dpsec:Mac:descr managed object property"
    ::= { cucsDpsecMacEntry 4 }

cucsDpsecMacForge OBJECT-TYPE
    SYNTAX       CucsDpsecForgedTransmit
    MAX-ACCESS   read-only
    STATUS       current
    DESCRIPTION
        "Cisco UCS dpsec:Mac:forge managed object property"
    ::= { cucsDpsecMacEntry 5 }

cucsDpsecMacIntId OBJECT-TYPE
    SYNTAX       SnmpAdminString
    MAX-ACCESS   read-only
    STATUS       current
    DESCRIPTION
        "Cisco UCS dpsec:Mac:intId managed object property"
    ::= { cucsDpsecMacEntry 6 }

cucsDpsecMacName OBJECT-TYPE
    SYNTAX       SnmpAdminString
    MAX-ACCESS   read-only
    STATUS       current
    DESCRIPTION
        "Cisco UCS dpsec:Mac:name managed object property"
    ::= { cucsDpsecMacEntry 7 }

cucsDpsecMacPolicyLevel OBJECT-TYPE
    SYNTAX       Gauge32
    MAX-ACCESS   read-only
    STATUS       current
    DESCRIPTION
        "Cisco UCS dpsec:Mac:policyLevel managed object property"
    ::= { cucsDpsecMacEntry 8 }

cucsDpsecMacPolicyOwner OBJECT-TYPE
    SYNTAX       CucsPolicyPolicyOwner
    MAX-ACCESS   read-only
    STATUS       current
    DESCRIPTION
        "Cisco UCS dpsec:Mac:policyOwner managed object property"
    ::= { cucsDpsecMacEntry 9 }

END
